(defun tee-insert ( / old-osmode)
    (setq old-osmode (getvar "OSMODE"))
    (defun *error* (message)
        (princ)
        (princ message)
        (princ)
        (setvar "OSMODE" old-osmode)
        (setvar "LWDISPLAY" 1)
    )
    (setvar "INSUNITS" 0) ;This line prevents inserted block refs from having a different scale, being 12 time bigger than they should be
    (setvar "OSMODE" 0)
    (command "-LAYER" "NEW" "Tees" "")
    (command "-LAYER" "COLOR" "White" "Tee" "")
    (setvar "LWDISPLAY" 0)
    (command "-LAYER" "SET" "Tees" "")
    (command "-INSERT" "Tee.dwg" pause 1.0 1.0 0)  
)
