(defun tee-insert ( / old-osmode)
    (setq old-osmode (getvar "OSMODE"))
    (defun *error* (message)
        (princ)
        (princ message)
        (princ)
        (setvar "OSMODE" old-osmode)
        (setvar "LWDISPLAY" 1)
        (command "-COLOR" "BYLAYER")
        (command "-LAYER" "SET" "0" "")
    )
    
    (setvar "INSUNITS" 1) ; 0 = not set, 1 = inches, 2 = feet
    (setvar "OSMODE" osmode-snap-ins-pts)
    (setvar "LWDISPLAY" 0)
    (command "-LAYER" "SET" "Tees" "")
    (command "-INSERT" "Tee.dwg" pause 1.0 1.0 0)  
    
    (setvar "OSMODE" old-osmode)
    (command-s "-LAYER" "SET" "0" "")
    (setvar "LWDISPLAY" 1)
)

(defun domestic-tee-insert ( / old-osmode)
    (setq old-osmode (getvar "OSMODE"))
    (defun *error* (message)
        (princ)
        (princ message)
        (princ)
        (setvar "OSMODE" old-osmode)
        (setvar "LWDISPLAY" 1)
        (command "-COLOR" "BYLAYER")
        (command "-LAYER" "SET" "0" "")
    )
    (setvar "INSUNITS" 1) ; 0 = not set, 1 = inches, 2 = feet
    (setvar "OSMODE" osmode-snap-ins-pts)
    (command "-LAYER" "NEW" "DomesticTees" "")
    (command "-LAYER" "COLOR" "White" "Tee" "")
    (setvar "LWDISPLAY" 0)
    (command "-LAYER" "SET" "DomesticTees" "")
    (command "-INSERT" "DomesticTee.dwg" pause 1.0 1.0 0)  
)
