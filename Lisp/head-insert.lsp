; TODO: Maybe have two parameters: model-code and filename, use a separate function to determine them.
(defun head-insert (model coverage slope temperature / model-code pt)
  (setq old-osmode (getvar "OSMODE"))
  (setq temperror *error*)
  (defun *error* (message)
	  (princ)
	  (princ message)
	  (princ)
    (setvar "OSMODE" old-osmode)
	(command "-LAYER" "OFF" "HeadCoverage" "")
    (setvar "LWDISPLAY" 1)
	(setq *error* temperror)
  )
  (setvar "INSUNITS" 0) ;This line prevents inserted block refs from having a
                        ;different scale, being 12 times bigger than they should be.
  (setvar "OSMODE" 0)
  (command "-LAYER" "NEW" "Heads" "")
  (command "-LAYER" "NEW" "HeadCoverage" "")
  (command "-LAYER" "COLOR" "Red" "Heads" "")
  (command "-LAYER" "COLOR" "Yellow" "HeadCoverage" "")
  (command "-LAYER" "ON" "HeadCoverage" "")
  (setvar "LWDISPLAY" 0)
  (command "-LAYER" "SET" "Heads" "")
  (while T
	(setq model-code "HEAD-X")
;
;   This section is for heads that you already know the coverage
;   Now the default is that you don't know. 
;   See the head-insert.lsp file and the head-insert function. 
;
;   (setq model-code (model-code-from model coverage slope temperature))
;	(prompt (strcat "\nInserting Head Model Code: " model-code "\n"))
;   (prompt "\nPress Esc to quit inserting heads.\n")
;	(command "-INSERT" (strcat "Head" coverage ".dwg") pause 1.0 1.0 0 model-code)
;
	(command "-INSERT" (strcat "Head12-20.dwg") pause 1.0 1.0 0 model-code)
	(setq pt (cdr (assoc 10 (entget (entlast)))))
	(if (null global:head-coverage)
		(setq global:head-coverage "16")
	)
	(initget "12 14 16 18 20")
	(if (setq tmp (getkword (strcat "\nHead Coverage [12/14/16/18/20] <" global:head-coverage ">: ")))
		(setq global:head-coverage tmp)
	)
	(entdel (entlast))
	(setq model-code (model-code-from model global:head-coverage slope temperature))
	(prompt (strcat "\nInserting Head Model Code: " model-code "\n"))
    (prompt "\nPress Esc to quit inserting heads.\n")
	(command "-INSERT" (strcat "Head" global:head-coverage ".dwg") pt 1.0 1.0 0 model-code)
  )
)

(defun model-code-from (model coverage slope temperature)
	(cond
		(
			(and 
				;(and model coverage slope temperature) 
				(> (strlen model) 0)
				(> (strlen coverage) 0)
				(> (strlen slope) 0)
				(> (strlen temperature) 0)
			)
			(strcat model "-" coverage "-" slope "-" temperature)
		)
		(
			(and 
				(> (strlen model) 0)
				(> (strlen coverage) 0)
				(> (strlen slope) 0)
			)
			(strcat model "-" coverage "-" slope)
		)
		(			
			(and 
				(> (strlen model) 0)
				(> (strlen coverage) 0)
			)
			(strcat model "-" coverage)
		)
		(
			(> (strlen model) 0)
			(strcat model)
		)
	)
)
