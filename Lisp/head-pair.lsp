(defun head-pair ( / old-osmode old-orthomode)
    (setq old-osmode (getvar "OSMODE"))
    (setq old-orthomode (getvar "ORTHOMODE"))
    (*push-error-using-command*)
    (defun *error* (message)
        (princ)
        (princ message)
        (princ)
        (setvar "OSMODE" old-osmode)
        (setvar "ORTHOMODE" old-orthomode)
        (command-s "-COLOR" "BYLAYER")
        (command-s "-LAYER" "SET" "0" "")
    )
    (setvar "INSUNITS" 1) ;This line prevents inserted block refs from having 
    ; a different scale, being 12 time bigger than they should be
    (setvar "OSMODE" 0)
    (command-s "-LAYER" "ON" "HeadPairs" "")
    (setvar "LWDISPLAY" 0)
    (command-s "-LAYER" "SET" "HeadPairs" "")
    (setvar "OSMODE" 64) ; 64 = Snap to insertion points
    (setvar "ORTHOMODE" 0)
    (command-s "-COLOR" "BYLAYER")
    (prompt "\nDraw a line between each head pair.\n")
    (command-s "_LINE" pause)
    
    (prompt "Press the [ENTER] key or right click model space to repeat")
  
    (setvar "OSMODE" old-osmode)
    (command-s "-LAYER" "OFF" "HeadCoverage" "")
    (command-s "-LAYER" "SET" "0" "")
    (setvar "LWDISPLAY" 1)
)
