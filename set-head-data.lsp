(defun set-head-model () 
	(submit-data "DefaultHeadModel" (getstring "\nEnter Default Head Model: "))
	(princ)
)
(defun set-head-coverage () 
	(submit-data "DefaultHeadCoverage" (getstring "\nEnter Default Head Coverage: "))
	(princ)
)
(defun set-head-slope () 
	(submit-data "DefaultHeadSlope" (getstring "\nEnter Default Head Slope: "))
	(princ)
)
(defun set-head-temperature () 
	(submit-data "DefaultHeadTemperature" (getstring "\nEnter Default Head Temperature: "))
	(princ)
)
(defun set-head-data () 
	(set-head-model)
	(set-head-coverage)
	(set-head-slope)
	(set-head-temperature)
)
