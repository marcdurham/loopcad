(defun insert-head (model coverage slope temperature)
  (setq old-osmode (getvar "OSMODE"))
  (defun *error* (message)
	  (princ)
	  (princ message)
	  (princ)
    (setvar "OSMODE" old-osmode)
	  (command "-LAYER" "OFF" "HeadCoverage" "")
    (setvar "LWDISPLAY" 1)
  )
  (setvar "INSUNITS" 0) ;This line prevents inserted block refs from having a different scale, being 12 time bigger than they should be
  (setvar "OSMODE" 0)
  (command "-LAYER" "NEW" "Heads" "")
  (command "-LAYER" "NEW" "HeadCoverage" "")
  (command "-LAYER" "COLOR" "Red" "Heads" "")
  (command "-LAYER" "COLOR" "Yellow" "HeadCoverage" "")
  (command "-LAYER" "ON" "HeadCoverage" "")
  (setvar "LWDISPLAY" 0)
  (command "-LAYER" "SET" "Heads" "")
  (while T
    (setq model-code (strcat model coverage "-" slope "-" temperature))
	(prompt (strcat "\nInserting Head Model Code: " model-code "\n"))
    (prompt "\nPress Esc to quit inserting heads.\n")
    (command "-INSERT" (strcat "Head" coverage ".dwg") pause 1.0 1.0 0 model-code)
  )
)
