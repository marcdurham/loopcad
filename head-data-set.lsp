(defun head-model-set () 
	(data-submit "DefaultHeadModel" (getstring "\nEnter Default Head Model: "))
	(princ)
)
(defun head-coverage-set () 
	(data-submit "DefaultHeadCoverage" (getstring "\nEnter Default Head Coverage: "))
	(princ)
)
(defun head-slope-set () 
	(data-submit "DefaultHeadSlope" (getstring "\nEnter Default Head Slope: "))
	(princ)
)
(defun head-temperature-set () 
	(data-submit "DefaultHeadTemperature" (getstring "\nEnter Default Head Temperature: "))
	(princ)
)
(defun head-data-set () 
	(head-model-set)
	(head-coverage-set)
	(head-slope-set)
	(head-temperature-set)
)
