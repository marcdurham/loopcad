(defun C:SET-HEAD-DATA () (head-data-set))
(defun C:SET-HEAD-MODEL () (head-model-set))
(defun C:SET-HEAD-COVERAGE () (head-coverage-set))
(defun C:SET-HEAD-SLOPE () (head-slope-set))
(defun C:SET-HEAD-TEMP () (head-temperature-set))
(defun C:HEAD () (head-insert-user))
(defun C:HEAD-12 () (head-insert-coverage "12"))
(defun C:HEAD-14 () (head-insert-coverage "14"))
(defun C:HEAD-16 () (head-insert-coverage "16"))
(defun C:HEAD-18 () (head-insert-coverage "18"))
(defun C:HEAD-20 () (head-insert-coverage "20"))
(defun C:PIPE () (pipe-draw (getstring "Enter Pipe Size: ")))
(defun C:PIPE-12 () (pipe-draw "1/2"))
(defun C:PIPE-34 () (pipe-draw "3/4"))
(defun C:PIPE-1 () (pipe-draw "1"))
(defun C:PIPE-114 () (pipe-draw "1-1/4"))
(defun C:ELEVATION-BOX () (vl-vbarun "Controller.ElevationBox"))
(defun C:TEE () (tee-insert))
